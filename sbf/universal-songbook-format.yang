module universal-songbook-format {
  yang-version "1";
  namespace "http://yang.jmq.cz/universal-songbook-format";
  prefix "sbf";

  organization "SongBook working group";
  contact
    "Maria Matejka
    mq@jmq.cz";
  
  description "Container for play-along and sing-along songbooks";

  grouping segment {
    leaf key {
      type int32;
    }
    leaf lyrics {
      type string;
    }
    leaf chord {
      type string;
    }
  }

  grouping line {
    leaf key {
      type int32;
    }
    list segments {
      key "key";
      uses segment;
      ordered-by user;
    }
  }

  grouping block {
    leaf name {
      type string;
    }
    choice lines {
      leaf ref {
	type leafref {
	  path "../../blocks/name";
	}
      }
      list lines {
	key "key";
	uses line;
	ordered-by user;
      }
    }
  }

  grouping songbook-grouping {
    description "Top-level songbook structure";

    list songs {
      description "Top-level song structure";

      key "title";

      leaf title {
	type string;
	description "Song title";
      }

      leaf-list authors {
	description "Author list";
	type leafref {
	  path "../../authors/name";
	}
      }

      list blocks {
	description "Named song blocks";
	key "name";
	uses block;
      }
    }

    list authors {
      description "Author object";
      key "name";

      leaf name {
        type string;
        description "Author name";
      }
    }
  }

  container songbook {
    uses songbook-grouping;
  }
}
